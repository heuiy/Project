;; 240416 다시 시작

;; 1장 저장됨, 가로로 출력됨

(defun c:plotall ()
 (setq flt
   '(
     (-4 . ">(0 . \"LWPOLYLINE\")")
     (8 . "KHUNGTEN")
     (90 . 4)
     (70 . 1)
     (-4 . "AND>")
   )
 )
 (if (setq ss (ssget "X" flt))
   (progn
     (setq sl (sslength ss))
     (setq s1 0)
     (while (< s1 sl)
       (setq dt2 (ssname ss s1))
       (setq A (entget dt2))
       (setq j 14)
       (while (/= (car (nth j A)) 10)
         (setq j (1+ j))
       )
       (setq DINH1 (cdr (nth j A)))
       (setq DINH2 (cdr (nth (+ j 4) A)))
       (setq DINH3 (cdr (nth (+ j 8) A)))
       (setq DINH4 (cdr (nth (+ j 12) A)))
       (setq GOC1 (ANGLE DINH1 DINH2))
       (setq GOC2 (ANGLE DINH2 DINH3))
       (setq GOC3 (ANGLE DINH3 DINH4))
       (setq GOC4 (ANGLE DINH4 DINH1))
       (setq KC12 (DISTANCE DINH1 DINH2))
       (setq KC14 (DISTANCE DINH1 DINH4))
       (if (= (distance DINH1 DINH3) (distance DINH2 DINH4))
         (progn
           (cond
             ((and (= GOC1 0) (> KC12 KC14))
               (command "-plot" "Y" "" "" "Landscape" "Y"))
             ((and (= GOC1 pi) (> KC12 KC14))
               (command "-plot" "Y" "" "" "Landscape" "Y"))
             ((and (= GOC1 (/ pi 2)) (< KC12 KC14))
               (command "-plot" "Y" "" "" "Landscape" "Y"))
             ((and (= GOC1 (* pi 1.5)) (< KC12 KC14))
               (command "-plot" "Y" "" "" "Landscape" "Y"))
             ((and (= GOC1 (/ pi 2)) (> KC12 KC14))
               (command "-plot" "Y" "" "" "Portrait" "Y"))
             ((and (= GOC1 (* pi 1.5)) (> KC12 KC14))
               (command "-plot" "Y" "" "" "Portrait" "Y"))
             ((and (= GOC1 0) (< KC12 KC14))
               (command "-plot" "Y" "" "" "Portrait" "Y"))
             ((and (= GOC1 pi) (< KC12 KC14))
               (command "-plot" "Y" "" "" "Portrait" "Y"))
           )
         )
       )
       (setq s1 (+ s1 1))
     )
     (princ "\nPlotting done.")
   )
   (princ "\nNo objects plotting. You need repeat command.")
 )
 (princ)
)
​​
